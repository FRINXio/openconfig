module frinx-acl-extension {

  yang-version "1";

  // namespace
  namespace "http://frinx.openconfig.net/yang/acl/ext";

  prefix "oc-acl-ext";

  // import some basic types
  import frinx-openconfig-acl { prefix "oc-acl"; }
  import frinx-openconfig-inet-types { prefix oc-inet; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Extension to Acces Control List (ACL) implementation
    based on OpenConfig";

  revision "2018-03-14" {
    description
      "Initial release";
  }

  typedef hop-range {
    type string {
    // 0-255..0-255
    pattern '(25[0-5]|2[0-4][0-9]|[0-1]?[0-9]?[0-9]?)' +
        '\.\.' +
        '(25[0-5]|2[0-4][0-9]|[0-1]?[0-9]?[0-9]?)';
    }
    description
      "Hop count represented in inclusive range as
      <lower>..<higher>";
  }

  typedef icmp-msg-type {
    type union {
      type uint8 {
        range 0..255;
      }
      type enumeration {
        enum ANY {
          description
            "Indicates not specified message type";
        }
      }
    }
    description "ICMP message type";
  }

  grouping acl-hop-range {
    leaf hop-range {
      type hop-range;
      description
        "The IP packet's hop range (TTL)";
    }
  }

  grouping acl-icmp-type {
    container icmp {
      container config {
        leaf msg-type {
          type icmp-msg-type;
          description
            "ICMP message type";
        }
      }
    }
  }

  grouping ipv4-address-wildcarded {
    leaf address {
      type oc-inet:ipv4-address;
      description
        "IPv4 address.";
    }
    leaf wildcard-mask {
      type oc-inet:ipv4-address;
      description
        "IPv4 wildcard mask.";
    }
  }

  grouping src-dst-ipv4-address-wildcarded {
    description
      "Configuration data of IP protocol fields
      for IPv4";
    container source-address-wildcarded {
      uses ipv4-address-wildcarded;
    }
    container destination-address-wildcarded {
      uses ipv4-address-wildcarded;
    }
  }

  grouping ipv6-address-wildcarded {
    leaf address {
      type oc-inet:ipv6-address;
      description
        "IPv6 address.";
    }
    leaf wildcard-mask {
      type oc-inet:ipv6-address;
      description
        "IPv6 wildcard mask.";
    }
  }

  grouping src-dst-ipv6-address-wildcarded {
    description
      "Configuration data of IP protocol fields
      for IPv6";
    container source-address-wildcarded {
      uses ipv6-address-wildcarded;
    }
    container destination-address-wildcarded {
      uses ipv6-address-wildcarded;
    }
  }

  grouping src-dst-port-named {
    description
      "Configuration data of transport fields";
    leaf source-port-named {
      type string;
      description
        "Source port represented by name.";
    }
    leaf destination-port-named {
      type string;
      description
        "Destination port represented by name.";
    }
  }

  grouping established-state {
    description
      "Configuration data of established state";
    leaf established {
      type boolean;
      description
        "Allows TCP traffic to pass if packet is a reply to an outbound initiated session.";
    }
  }

  grouping term-name {
    description
      "Configuration data of terminal name";
    leaf term-name {
      type string;
      description
        "terminal name";
    }
  }

  grouping instance-name {
    description
      "Configuration data of action instance name";
    leaf instance-name {
      type string;
      description
        "action instance name";
    }
  }

  grouping acl-set-extension-config {
    leaf default-fwd-action {
      type identityref {
        base oc-acl:FORWARDING_ACTION;
      }
      description "The default filter action on the acl profile.";
    }

    leaf enabled {
      type boolean;
        description "Enable/disable an ACL profile.";
    }
  }

  grouping acl-set-extension-config-vrp {
    leaf type2 {
      type string;
      description "Enable/disable an ACL profile.";
    }
    leaf description {
      type string;
      description "Specify ACL description.";
    }
    leaf step {
      type string;
      description "Specify step of ACL sub rule ID.";
    }
  }

  grouping acl-set-precedence {
    description
      "Configuration of precedence.";
    leaf precedence {
      type enumeration {
        enum ROUTINE {
          description "Match packets with routine precedence.";
        }
        enum PRIORITY {
          description "Match packets with priority precedence.";
        }
        enum IMMEDIATE {
          description "Match packets with immediate precedence.";
        }
        enum FLASH {
          description "Match packets with flash precedence.";
        }
        enum FLASH-OVERRIDE {
          description "Match packets with flash override precedence.";
        }
        enum CRITICAL {
          description "Match packets with critical precedence.";
        }
        enum INTERNET {
          description "Match packets with internetwork control precedence.";
        }
        enum NETWORK {
          description "Match packets with network control precedence.";
        }
      }
      description "Precedence setting for extended acl.";
    }
  }

  grouping acl-set-option {
    description
      "Configuration of options.";
    leaf option {
      type union {
        type uint8 {
          range "0 .. 255";
        }
        type enumeration {
          enum ADD-EXT {
            description "Match packets with Address Extension Option.";
          }
          enum ANY-OPTIONS {
            description "Match packets with ANY Option.";
          }
          enum COM-SECURITY {
            description "Match packets with Commercial Security Option.";
          }
          enum DPS {
            description "Match packets with Dynamic Packet State Option.";
          }
          enum ENCODE {
            description "Match packets with Encode Option.";
          }
          enum EOOL {
            description "Match packets with End of Options.";
          }
          enum EXT-IP {
            description "Match packets with Extended IP Option.";
          }
          enum EXT-SECURITY {
            description "Match packets with Extended Security Option.";
          }
          enum FINN {
            description "Match packets with Experimental Flow Control Option.";
          }
          enum IMITD {
            description "Match packets with IMI Traffic Descriptor Option.";
          }
          enum LSR {
            description "Match packets with Loose Source Route Option.";
          }
          enum MTUP {
            description "Match packets with MTU Probe Option.";
          }
          enum MTUR {
            description "Match packets with MTU Reply Option.";
          }
          enum NO-OP {
            description "Match packets with No Operation Option.";
          }
          enum NSAPA {
            description "Match packets with NSAP Addresses Option.";
          }
          enum RECORD-ROUTE {
            description "Match packets with Record Route Option.";
          }
          enum ROUTER-ALERT {
            description "Match packets with Router Alert Option.";
          }
          enum SDB {
            description "Match packets with Selective Directed Broadcast Option.";
          }
          enum SECURITY {
            description "Match packets with Basic Security Option.";
          }
          enum SSR {
            description "Match packets with Strict Source Routing Option.";
          }
          enum STREAM-ID {
            description "Match packets with Stream ID Option.";
          }
          enum TIMESTAMP {
            description "Match packets with Time Stamp Option.";
          }
        }
      }
    }
  }

  identity ACL_IPV4_STANDARD {
    base oc-acl:ACL_TYPE;
    description
      "Standard IPv4 ACL allows to control
      traffic only by the source IP address.";
  }

  identity ACL_IPV4_EXTENDED {
    base oc-acl:ACL_TYPE;
    description
      "Extended IPv4 ACL allows to control
      traffic by the source and destination
      IP address.";
  }

  // augment statements
  augment "/oc-acl:acl/oc-acl:acl-sets/oc-acl:acl-set/oc-acl:acl-entries/oc-acl:acl-entry/oc-acl:transport/oc-acl:config" {
    ext:augment-identifier "acl-set-acl-entry-transport-port-named-aug";
    uses src-dst-port-named;
  }

  augment "/oc-acl:acl/oc-acl:acl-sets/oc-acl:acl-set/oc-acl:acl-entries/oc-acl:acl-entry/oc-acl:ipv4/oc-acl:config" {
    ext:augment-identifier "acl-set-acl-entry-ipv4-wildcarded-aug";
    uses src-dst-ipv4-address-wildcarded;
  }

  augment "/oc-acl:acl/oc-acl:acl-sets/oc-acl:acl-set/oc-acl:acl-entries/oc-acl:acl-entry/oc-acl:ipv6/oc-acl:config" {
    ext:augment-identifier "acl-set-acl-entry-ipv6-wildcarded-aug";
    uses src-dst-ipv6-address-wildcarded;
  }

  augment "/oc-acl:acl/oc-acl:acl-sets/oc-acl:acl-set/oc-acl:acl-entries/oc-acl:acl-entry/oc-acl:ipv4/oc-acl:config" {
    uses acl-hop-range;
  }

  augment "/oc-acl:acl/oc-acl:acl-sets/oc-acl:acl-set/oc-acl:acl-entries/oc-acl:acl-entry/oc-acl:ipv6/oc-acl:config" {
    uses acl-hop-range;
  }

  augment "/oc-acl:acl/oc-acl:acl-sets/oc-acl:acl-set/oc-acl:acl-entries/oc-acl:acl-entry" {
    uses acl-icmp-type;
  }

  augment "/oc-acl:acl/oc-acl:acl-sets/oc-acl:acl-set/oc-acl:acl-entries/oc-acl:acl-entry/oc-acl:config" {
    description "Adds terminal name to acl-entry config";
    uses term-name;
  }

  augment "/oc-acl:acl/oc-acl:acl-sets/oc-acl:acl-set/oc-acl:acl-entries/oc-acl:acl-entry/oc-acl:actions/oc-acl:config" {
    description "Adds instance name of actions in acl-entry";
    uses instance-name;
  }

  augment "/oc-acl:acl/oc-acl:acl-sets/oc-acl:acl-set/oc-acl:config" {
    description "Adds SAOS specific configuration to acl model";
    ext:augment-identifier "saos-6-acl-set-aug";
    uses acl-set-extension-config;
  }

  augment "/oc-acl:acl/oc-acl:acl-sets/oc-acl:acl-set/oc-acl:config" {
    description "Adds HUAWEI specific configuration to acl model";
    ext:augment-identifier "vrp-acl-set-aug";
    uses acl-set-extension-config-vrp;
  }

  augment "/oc-acl:acl/oc-acl:acl-sets/oc-acl:acl-set/oc-acl:acl-entries/oc-acl:acl-entry" {
    description "Precedence augmentation for iOs devices.";
    ext:augment-identifier "acl-precedence-aug";
    uses acl-set-precedence;
  }

  augment "/oc-acl:acl/oc-acl:acl-sets/oc-acl:acl-set/oc-acl:acl-entries/oc-acl:acl-entry" {
    description "Options augmentation for iOs devices.";
    ext:augment-identifier "acl-option-aug";
    uses acl-set-option;
  }

  augment "/oc-acl:acl/oc-acl:acl-sets/oc-acl:acl-set/oc-acl:acl-entries/oc-acl:acl-entry/oc-acl:transport/oc-acl:config" {
    description "Established state augmentation.";
    ext:augment-identifier "acl-established-state-aug";
    uses established-state;
  }

  // uniconfig augmentations
  augment "/nt:network-topology/nt:topology/nt:node/ut:configuration/oc-acl:acl/oc-acl:acl-sets/oc-acl:acl-set/oc-acl:acl-entries/oc-acl:acl-entry/oc-acl:transport/oc-acl:config" {
    uses src-dst-port-named;
  }

  augment "/nt:network-topology/nt:topology/nt:node/ut:configuration/oc-acl:acl/oc-acl:acl-sets/oc-acl:acl-set/oc-acl:acl-entries/oc-acl:acl-entry/oc-acl:ipv4/oc-acl:config" {
    uses src-dst-ipv4-address-wildcarded;
  }

  augment "/nt:network-topology/nt:topology/nt:node/ut:configuration/oc-acl:acl/oc-acl:acl-sets/oc-acl:acl-set/oc-acl:acl-entries/oc-acl:acl-entry/oc-acl:ipv6/oc-acl:config" {
    uses src-dst-ipv6-address-wildcarded;
  }

  augment "/nt:network-topology/nt:topology/nt:node/ut:configuration/oc-acl:acl/oc-acl:acl-sets/oc-acl:acl-set/oc-acl:acl-entries/oc-acl:acl-entry/oc-acl:ipv4/oc-acl:config" {
    uses oc-acl-ext:acl-hop-range;
  }

  augment "/nt:network-topology/nt:topology/nt:node/ut:configuration/oc-acl:acl/oc-acl:acl-sets/oc-acl:acl-set/oc-acl:acl-entries/oc-acl:acl-entry/oc-acl:ipv6/oc-acl:config" {
    uses oc-acl-ext:acl-hop-range;
  }

  augment "/nt:network-topology/nt:topology/nt:node/ut:configuration/oc-acl:acl/oc-acl:acl-sets/oc-acl:acl-set/oc-acl:acl-entries/oc-acl:acl-entry" {
    uses oc-acl-ext:acl-icmp-type;
  }

  augment "/nt:network-topology/nt:topology/nt:node/ut:configuration/oc-acl:acl/oc-acl:acl-sets/oc-acl:acl-set/oc-acl:acl-entries/oc-acl:acl-entry/oc-acl:config" {
    description "Adds terminal name to acl-entry config";
    uses term-name;
  }

  augment "/nt:network-topology/nt:topology/nt:node/ut:configuration/oc-acl:acl/oc-acl:acl-sets/oc-acl:acl-set/oc-acl:acl-entries/oc-acl:acl-entry/oc-acl:actions/oc-acl:config" {
    description "Adds instance name of actions in acl-entry";
    uses instance-name;
  }

  augment "/nt:network-topology/nt:topology/nt:node/ut:configuration/oc-acl:acl/oc-acl:acl-sets/oc-acl:acl-set/oc-acl:config" {
    description "Adds SAOS specific configuration to acl model";
    uses acl-set-extension-config;
  }

  augment "/nt:network-topology/nt:topology/nt:node/ut:configuration/oc-acl:acl/oc-acl:acl-sets/oc-acl:acl-set/oc-acl:config" {
    description "Adds HUAWEI specific configuration to acl model";
    uses acl-set-extension-config-vrp;
  }

  augment "/nt:network-topology/nt:topology/nt:node/ut:configuration/oc-acl:acl/oc-acl:acl-sets/oc-acl:acl-set/oc-acl:acl-entries/oc-acl:acl-entry" {
    description "Precedence augmentation for iOs devices.";
    uses acl-set-precedence;
  }

  augment "/nt:network-topology/nt:topology/nt:node/ut:configuration/oc-acl:acl/oc-acl:acl-sets/oc-acl:acl-set/oc-acl:acl-entries/oc-acl:acl-entry" {
    description "Options augmentations for iOs devices.";
    uses acl-set-option;
  }

  augment "/nt:network-topology/nt:topology/nt:node/ut:configuration/oc-acl:acl/oc-acl:acl-sets/oc-acl:acl-set/oc-acl:acl-entries/oc-acl:acl-entry/oc-acl:transport/oc-acl:config" {
    description "Established state augmentation.";
    uses established-state;
  }
}
