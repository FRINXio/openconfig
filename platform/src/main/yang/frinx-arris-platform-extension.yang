module frinx-arris-platform-extension {

  yang-version "1";

  // namespace
  namespace "http://frinx.openconfig.net/yang/platform/arris";

  prefix "arrisd-platform-extension";

  // import some basic types
  import frinx-openconfig-platform { prefix oc-platform; }
  // uniconfig imports
  import network-topology { prefix nt; revision-date "2013-10-21"; }
  import frinx-uniconfig-topology { prefix ut; revision-date "2017-11-21"; }
  import yang-ext { prefix ext; }

  // meta
  organization "Frinx s.r.o.";

  contact
    "support@frinx.io";

  revision "2022-11-24" {
    description
      "Initial release";
    reference "5.0.20";
  }

  grouping arris-platform-inventory-extension {

    description "Top level arris platform grouping";

    container lldp {

      description "Arris platform lldp container";

      leaf lldp-status {
        type string;
        description "LLDP status information";
      }

      leaf lldp-ad-interval {
        type string;
        description "LLDP advertisements interval";
      }

      leaf lldp-ad-hold-time {
        type string;
        description "LLDP hold time advertised";
      }
    }

    container license {

      description "Arris platform license container";

      leaf system-legal-intercept {
        type boolean;
        description "System legal intercept";
      }

      leaf system-principal-core {
        type boolean;
        description "System principal core";
      }

      leaf system-auxiliary-core {
        type boolean;
        description "System auxiliary core";
      }

      leaf system-laes {
        type boolean;
        description "System laes";
      }

      leaf system-calea {
        type boolean;
        description "System calea";
      }

      leaf system-lld-us-asf {
        type boolean;
        description "System lld us asf";
      }

      leaf system-us-pgs {
        type boolean;
        description "System us pgs";
      }

      leaf chassis-serial-number {
        type string;
        description "Chassis serial number";
      }
    }

    container transceiver {

      description "Arris platform transceiver container";

      leaf t-type {
        type string;
        description "T Type";
      }

      leaf speed {
        type string;
        description "Speed";
      }

      leaf type {
        type string;
        description "Type";
      }

      leaf vendor {
        type string;
        description "Vendor";
      }

      leaf part-number {
        type string;
        description "Part number";
      }

      leaf revision {
        type string;
        description "Revision";
      }

      leaf serial-number {
        type string;
        description "Serial number";
      }

      leaf date-code {
        type string;
        description "Date code";
      }

      leaf temperature {
        type string;
        description "Temperature";
      }

      leaf voltage {
        type string;
        description "Voltage";
      }

      leaf ch-0-tx-bias {
        type string;
        description "Channel 0 txBias";
      }

      leaf ch-0-tx-power {
        type string;
        description "Channel 0 txPower";
      }

      leaf ch-0-rx-power {
        type string;
        description "Channel 0 rxPower";
      }
    }

    container chassis {

      description "Arris platform chassis container";

      leaf model-name {
        type string;
        description "Model name";
      }

      leaf model-version {
        type string;
        description "Model version";
      }

      leaf serial-number {
        type string;
        description "Serial number";
      }

      leaf chassis-type {
        type string;
        description "Chassis type";
      }
    }

    container version-detail {

      description "Arris platform chassis version detail container";

      leaf type {
        type string;
        description "Type";
      }

      leaf model-name {
        type string;
        description "Model name";
      }

      leaf model-version {
        type string;
        description "Model version";
      }

      leaf serial-number {
        type string;
        description "Serial number";
      }

      leaf cpu-speed {
        type string;
        description "CPU speed";
      }

      leaf bus-speed {
        type string;
        description "Bus speed";
      }

      leaf ram-size {
        type string;
        description "RAM size";
      }

      leaf nor-flash-size {
        type string;
        description "NOR flash type";
      }

      leaf nand-flash-size {
        type string;
        description "NAND flash type";
      }

      leaf pic-model-name {
        type string;
        description "PIC model name";
      }

      leaf pic-model-version {
        type string;
        description "PIC model version";
      }

      leaf pic-serial-number {
        type string;
        description "PIC serial number";
      }

      leaf firmware-version {
        type string;
        description "Firmware version";
      }

      leaf active-sw {
        type string;
        description "Active SoftWare";
      }

      leaf active-patch {
        type string;
        description "Active patch";
      }

      leaf reason-last-booted {
        type string;
        description "Reason last booted";
      }

      leaf uptime {
        type string;
        description "Uptime";
      }

      leaf last-booted-time {
        type string;
        description "TIme since CMTS was last booted";
      }

      leaf exec-time {
        type string;
        description "Execution time";
      }
    }
  }

  // augment statements

  augment "/oc-platform:components/oc-platform:component/oc-platform:state" {
    description "Adding some data from operational state inventory";
    ext:augment-identifier "arris-platform-aug";

    uses arris-platform-inventory-extension;
  }

  // uniconfig augmentations

  augment "/nt:network-topology/nt:topology/nt:node/ut:configuration/oc-platform:components/oc-platform:component/oc-platform:state" {
    description "Adding some data from operational state inventory";

    uses arris-platform-inventory-extension;
  }
}
