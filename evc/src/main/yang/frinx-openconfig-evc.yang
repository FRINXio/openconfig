module frinx-openconfig-evc {

  yang-version "1";

  // namespace
  namespace "http://frinx.openconfig.net/yang/evc";

  prefix "evc";

  // uniconfig imports
  import network-topology { prefix nt; revision-date "2013-10-21"; }
  import frinx-uniconfig-topology { prefix ut; revision-date "2017-11-21"; }

  // meta
  organization "Frinx s.r.o";

  contact
    "support@frinx.io";

  description
    "Model for managing evc";

  revision "2020-04-16" {
    description
      "Initial release";
    reference "4.2.4";
  }

  grouping evc-top {
    description "Top-level grouping for evc";

    container evcs {
      description "Container objects of evc";

      list evc {
        key "name";

        description "List of evcs";

        leaf name {
          type leafref {
            path "../config/name";
          }

          description "The name of the evc";
        }

        container config {
          description "Configured reference to evc";

          leaf name {
            type string;

            description "The name of the evc";
          }
        }
      }
    }
  }

  uses evc-top;

  // uniconfig augmentations

  augment "/nt:network-topology/nt:topology/nt:node/ut:configuration" {
    description "Added evc to configuration";
    uses evc-top;
  }
}
