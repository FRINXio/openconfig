module frinx-huawei-banner-extension {

  yang-version "1";

  // namespace
  namespace "http://frinx.openconfig.net/yang/system/huawei-banner-extension";

  prefix "huawei-banner-ext";

  // import some basic types
  import frinx-openconfig-system { prefix oc-sys; }

  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig banner models,
    containing HUAWEI specific features.";

  revision "2021-10-11" {
    description
      "Initial release";
    reference "4.2.9";
  }

  grouping huawei-banner-top {
    description "Top-level grouping for banner";

    container banner {
      description "Top-level container for banner configuration";

      container config {
        description "Configuration data for banner";

        leaf banner-text {
          type string;
          description "Banner text for device.";
        }
      }
    }
  }

  augment "/oc-sys:system" {
    description "Banner augmentation";
    ext:augment-identifier "banner-huawei-aug";

    uses huawei-banner-top;
  }

  augment "/nt:network-topology/nt:topology/nt:node/ut:configuration/oc-sys:system" {
    description "Banner augmentation";

    uses huawei-banner-top;
  }
}
