module snmp {

  yang-version "1";

  // namespace
  namespace "http://frinx.io/yang/snmp";

  prefix "snmp";

  // import some basic types
  import openconfig-interfaces { prefix oc-if; }
  import event-types { prefix event-types; }

  // meta
  organization "Frinx s.r.o";

  contact
    "support@frinx.io";

  description
    "SNMP interfaces implementation based on OpenConfig interfaces";

  revision "2017-10-24" {
    description
      "Initial release";
    reference "3.1.1";
  }

  // grouping statements

  grouping snmp-interfaces-structural {
    description
      "Structural grouping for interface to SNMP bindings.";

    container interfaces {
      description
        "Configuration and operational state relating SNMP
        on interfaces.";

      list interface {
        key "interface-id";

        description
          "Configuration and operationals state relating to the
          relationship between interfaces and SNMP.";

        leaf interface-id {
          type leafref {
            path "../config/interface-id";
          }
          description
            "A reference to the unique identifier for the interface
            being referenced by the SNMP.";
        }

        container config {
          description
            "Configuration parameters relating to an interface to
            SNMP binding.";

          uses snmp-interface-config;
        }

        container state {
          config false;
          description
            "Operational state parameters relating to an interface to
            SNMP binding.";

          uses snmp-interface-config;
          uses snmp-interface-state;
        }

        uses oc-if:interface-ref;
      }
    }
  }

  grouping snmp-interface-config {
    leaf interface-id {
      type oc-if:interface-id;
      description
        "A unique identifier for the interface.";
    }

    list enabled-trap-for-event {
      description
        "Event which triggers SNMP trap.";
      key event-name;
      leaf event-name {
        type identityref {
          base event-types:EVENT_TYPE;
        }
      }
    }
  }

  grouping snmp-interface-state {
    description
      "SNMP related operational state";

    //TODO: placeholder for operational state related to snmp
  }

  grouping snmp-top {
    description
      "Top-level grouping for snmp data";

    container snmp {
      description
        "Enclosing container for snmp interface-specific
        data.";

      uses snmp-interfaces-structural;
    }
  }

  // data definition statements

  uses snmp-top;
}
