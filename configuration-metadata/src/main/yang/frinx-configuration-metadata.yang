module frinx-configuration-metadata {
    yang-version "1";

    // namespace
    namespace "http://frinx.openconfig.net/yang/configuration-metadata";

    prefix "conf-meta";

    // uniconfig imports
    import network-topology { prefix nt; revision-date "2013-10-21"; }
    import yang-ext { prefix ext; revision-date "2013-07-09"; }

    description
        "Represents metadata about device configuration.";

    revision "2018-07-31" {
        description
            "Initial revision";
    }

    grouping metadata {
        container configuration-metadata {
            config false;

            leaf last-configuration-fingerprint {
                type string;
                description
                        "Unique fingerprint of last configuration.";
            }
        }
    }

    uses metadata;

    augment "/nt:network-topology/nt:topology/nt:node" {
        ext:augment-identifier "config-metadata-aug";

        uses metadata;
    }

}
