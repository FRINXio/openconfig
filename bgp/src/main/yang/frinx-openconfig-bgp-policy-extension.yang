module frinx-openconfig-bgp-policy-extension {

  yang-version "1";

  // namespace
  namespace "http://frinx.openconfig.net/yang/bgp-policy/policy-extension";

  prefix "oc-bgp-pol-ext";

  // import some basic types
  import frinx-openconfig-routing-policy { prefix oc-rpol; }
  import frinx-openconfig-bgp-policy { prefix oc-bgp-pol; }
  import frinx-openconfig-bgp-types { prefix oc-bgp-types; }

  // uniconfig imports
  import network-topology { prefix nt; revision-date "2013-10-21"; }
  import frinx-uniconfig-topology { prefix ut; revision-date "2017-11-21"; }
  import yang-ext { prefix ext; }

  // meta
  organization "Frinx s.r.o";

  contact
    "support@frinx.io";

  description
    "Model for managing bgp policy extension";

  revision "2021-05-25" {
    description
      "Initial release";
    reference "4.2.5";
  }

  identity SET_OPERATION {
    description
      "Value for route map to permit/deny set operations";
  }

  identity PERMIT {
    base SET_OPERATION;
    description
      "Route map permits set operations";
  }

  identity DENY {
    base SET_OPERATION;
    description
      "Route map denies set operations";
  }

  grouping community-members {
    description
      "Configuration community members with permission type deny";

    leaf-list community-member-deny {
      type union {
        type identityref {
          base oc-bgp-types:BGP_WELL_KNOWN_STD_COMMUNITY;
        }
        type oc-bgp-types:bgp-std-community-type;
        type oc-bgp-types:bgp-community-regexp-type;
      }
      description
        "Deny members of the community set";
    }
  }

  grouping cisco-rpol-extension-conditions {
    description "Match values from routing table";

    container match-ip-prefix-list {
      leaf-list ip-prefix-list {
        type string;
        description
          "IP specific information.";
      }
      leaf ipv6-prefix-list {
        type string;
        description
          "IPv6 specific information.";
      }
      leaf set-operation {
        type identityref {
          base SET_OPERATION;
        }
        description
          "Value for route map to permit/deny set operations.";
      }
    }
  }

  grouping match-community-config-list {
    leaf-list community-set-list {
      type string;
      description
        "IP specific information.";
    }
  }

  grouping cisco-tag-top {
    description
      "Top-level data definitions for list of tags which
      can be mathced in policies.";

    container tags {
      description
        "Enclosing container for list of tags which
        can be matcher in policies.";

      list tag {
        key "name";

        description "The List of tag-sets";

        leaf name {
          type leafref {
          path "../config/name";
          }
          description "Name of the tag-set";
        }

        container config {
          description "Configuration container for tag set";

          leaf name {
            type uint32;
            description "Tag set name";
          }
        }
      }
    }
  }

  augment "/oc-rpol:routing-policy/oc-rpol:defined-sets/oc-bgp-pol:bgp-defined-sets/oc-bgp-pol:community-sets/" +
         "oc-bgp-pol:community-set/oc-bgp-pol:config" {

    description "Extends community members deny type settings";
    ext:augment-identifier "comm-members-aug";
    uses community-members;
  }

  augment "/oc-rpol:routing-policy/oc-rpol:policy-definitions/oc-rpol:policy-definition/oc-rpol:statements
    /oc-rpol:statement/oc-rpol:conditions/oc-bgp-pol:bgp-conditions" {
    ext:augment-identifier "prefix-list-conditions-aug";
    description "Adds Cisco specific configuration to routing policy model";

    uses cisco-rpol-extension-conditions;
    uses cisco-tag-top;
  }

  augment "/oc-rpol:routing-policy/oc-rpol:policy-definitions/oc-rpol:policy-definition/oc-rpol:statements
    /oc-rpol:statement/oc-rpol:conditions/oc-bgp-pol:bgp-conditions/oc-bgp-pol:match-community-set/oc-bgp-pol:config" {
    ext:augment-identifier "match-community-config-list-aug";
    description "Adds Cisco specific configuration to routing policy model";

    uses match-community-config-list;
  }

  augment "/nt:network-topology/nt:topology/nt:node/ut:configuration/oc-rpol:routing-policy/oc-rpol:defined-sets/" +
        "oc-bgp-pol:bgp-defined-sets/oc-bgp-pol:community-sets/oc-bgp-pol:community-set/oc-bgp-pol:config" {

    description "Extends community members deny type settings";
    uses community-members;
  }

  augment "/nt:network-topology/nt:topology/nt:node/ut:configuration/oc-rpol:routing-policy/oc-rpol:policy-definitions
    /oc-rpol:policy-definition/oc-rpol:statements/oc-rpol:statement/oc-rpol:conditions/oc-bgp-pol:bgp-conditions" {
    description "Adds Cisco specific configuration to routing policy model";

    uses cisco-rpol-extension-conditions;
    uses cisco-tag-top;
  }

  augment "/nt:network-topology/nt:topology/nt:node/ut:configuration/oc-rpol:routing-policy/oc-rpol:policy-definitions
    /oc-rpol:policy-definition/oc-rpol:statements/oc-rpol:statement/oc-rpol:conditions/oc-bgp-pol:bgp-conditions" +
    "/oc-bgp-pol:match-community-set/oc-bgp-pol:config" {
    description "Adds Cisco specific configuration to routing policy model";

    uses match-community-config-list;
  }
}
