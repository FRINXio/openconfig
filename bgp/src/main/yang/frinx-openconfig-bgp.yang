module frinx-openconfig-bgp {

  yang-version "1";

  // namespace
  namespace "http://frinx.openconfig.net/yang/bgp";

  prefix "oc-bgp";

  // import some basic inet types
  import frinx-openconfig-extensions { prefix oc-ext; revision-date 2017-01-29; }

  // FI-227 : remove once fixed
  import frinx-openconfig-routing-policy { prefix oc-rpol; revision-date 2017-07-14; }

  // Include the OpenConfig BGP submodules
  // Common: defines the groupings that are common across more than
  //         one context (where contexts are neighbor, group, global)
  include frinx-openconfig-bgp-common { revision-date 2017-02-02; }
  // Multiprotocol: defines the groupings that are common across more
  //                than one context, and relate to Multiprotocol
  include frinx-openconfig-bgp-common-multiprotocol { revision-date 2017-02-02; }
  // Structure: defines groupings that are shared but are solely used for
  //            structural reasons.
  include frinx-openconfig-bgp-common-structure { revision-date "2017-02-02"; }
  // Include peer-group/neighbor/global - these define the groupings
  // that are specific to one context
  include frinx-openconfig-bgp-peer-group { revision-date 2017-02-02; }
  include frinx-openconfig-bgp-neighbor { revision-date 2017-02-02; }
  include frinx-openconfig-bgp-global { revision-date 2017-02-02; }

  // meta
  organization
    "OpenConfig working group";

  contact
    "OpenConfig working group
    netopenconfig@googlegroups.com";

  description
    "This module describes a YANG model for BGP protocol
    configuration.It is a limited subset of all of the configuration
    parameters available in the variety of vendor implementations,
    hence it is expected that it would be augmented with vendor-
    specific configuration data as needed. Additional modules or
    submodules to handle other aspects of BGP configuration,
    including policy, VRFs, VPNs, and additional address families
    are also expected.

    This model supports the following BGP configuration level
    hierarchy:

      BGP
        |
        +-> [ global BGP configuration ]
          +-> AFI / SAFI global
        +-> peer group
          +-> [ peer group config ]
          +-> AFI / SAFI [ per-AFI overrides ]
        +-> neighbor
          +-> [ neighbor config ]
          +-> [ optional pointer to peer-group ]
          +-> AFI / SAFI [ per-AFI overrides ]";

  oc-ext:openconfig-version "3.0.1";

  revision "2017-02-02" {
    description
      "Bugfix to remove remaining global-level policy data";
    reference "3.0.1";
  }

  revision "2017-01-26" {
    description
      "Add dynamic neighbor support, migrate to OpenConfig types";
    reference "3.0.0";
  }

  revision "2016-06-21" {
    description
      "OpenConfig BGP refactor";
    reference "2.1.1";
  }

  revision "2016-06-06" {
    description
      "OpenConfig public release";
    reference "2.1.0";
  }

  revision "2016-03-31" {
    description
      "OpenConfig public release";
    reference "2.0.1";
  }

  grouping bgp-top {
    description
      "Top-level grouping for the BGP model data";

    container bgp {
      description
        "Top-level configuration and state for the BGP router";

      container global {
        description
          "Global configuration for the BGP router";
          uses bgp-global-base;
      }

      container neighbors {
        description
          "Configuration for BGP neighbors";
        uses bgp-neighbor-list;
      }

      container peer-groups {
        description
          "Configuration for BGP peer-groups";
        uses bgp-peer-group-list;
      }
    }
  }

  // DEVIATION: use openconfig-network-instance:network-instances/network-instance/protocols/protocol/bgp
  // uses bgp-top;

}
