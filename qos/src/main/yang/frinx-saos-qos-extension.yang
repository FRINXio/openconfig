module frinx-saos-qos-extension {

  yang-version "1";

  // namespace
  namespace "http://frinx.openconfig.net/yang/qos/saos-extension";

  prefix "oc-saos-qos-ext";

  // import some basic types
  import frinx-openconfig-qos { prefix oc-qos; }
  import yang-ext { prefix ext; }
  // uniconfig imports
  import network-topology { prefix nt; revision-date "2013-10-21"; }
  import frinx-uniconfig-topology { prefix ut; revision-date "2017-11-21"; }

  // meta
  organization "Frinx s.r.o";

  contact
    "support@frinx.io";

  description
    "Set of augments needed to OpenConfig vlan models,
    containing saos specific features.";

  revision "2020-02-19" {
    description
      "Initial release";
    reference "4.2.4";
  }

  // grouping statements
  grouping saos-qos-extension-config {
    leaf enabled {
      type boolean;

      description "Enabled flag for qos config.";
    }
  }

  grouping saos-qos-if-extension-config {
    leaf enabled {
      type boolean;

      description "Enabled flag for qos interface config.";
    }
    leaf mode {
      type enumeration {
        enum none {
          description
            "type none";
        }
        enum advanced {
          description
            "type advanced";
        }
        enum standard-dot1dpri {
          description
            "type standard-dot1dpri";
        }
        enum standard-ip-prec {
          description
            "type standard-ip-prec";
        }
        enum standard-dscp {
          description
            "type standard-dscp";
        }
        enum standard-vlan {
          description
            "type standard-vlan";
        }
        enum standard-vlan-dot1dpri {
          description
            "type standard-vlan-dot1dpri";
        }
        enum standard-vlan-ip-prec {
          description
            "type standard-vlan-ip-prec";
        }
        enum standard-vlan-dscp {
          description
            "type standard-vlan-dscp";
        }
        enum hierarchical-port {
          description
            "type hierarchical-port";
        }
        enum hierarchical-vlan {
          description
            "type hierarchical-vlan";
        }
      }

      description "Profiling mode for qos interface config.";
    }
  }

  grouping saos-qos-scheduler-config {
    leaf type {
      type enumeration {
        enum port_policy {
          description
            "type port_policy";
        }
        enum queue_group_policy {
          description
            "type queue_group_policy";
        }
      }
      description
        "Scheduler type.";
    }
    leaf vs-name {
      type string;
        description
          "Virtual switch ethernet name";
    }
  }

  grouping saos-qos-sc-policy-config {
    leaf interface-id {
      type string;
      description
        "Identifier for the interface.";
    }
  }

  grouping saos-qos-2r3c-config {
    leaf congestion-avoidance {
      type string;
      description
        "Congestion avoidance profile name for traffic-services.";
    }
    leaf weight {
      type uint32;
      units bytes;
      description
        "Scheduler weight parameter for traffic-services";
    }
  }

  // augment statements
  augment "/oc-qos:qos/oc-qos:config" {
    ext:augment-identifier "saos-qos-aug";
    description "Adds saos specific configuration to qos config model";
    uses saos-qos-extension-config;
  }

  augment "/oc-qos:qos/oc-qos:interfaces/oc-qos:interface/oc-qos:config" {
    ext:augment-identifier "saos-qos-if-aug";
    description "Adds saos specific configuration to qos config model";
    uses saos-qos-if-extension-config;
  }

  augment "/oc-qos:qos/oc-qos:scheduler-policies/oc-qos:scheduler-policy/oc-qos:schedulers/oc-qos:scheduler/oc-qos:config" {
    ext:augment-identifier "saos-qos-scheduler-aug";
    description "Adds saos specific configuration to qos scheduler config model";
    uses saos-qos-scheduler-config;
  }

  augment "/oc-qos:qos/oc-qos:scheduler-policies/oc-qos:scheduler-policy/oc-qos:config" {
    ext:augment-identifier "saos-qos-sc-policy-ifc-id";
    description "Adds saos specific configuration to qos scheduler policy config model";
    uses saos-qos-sc-policy-config;
  }

  augment "/oc-qos:qos/oc-qos:scheduler-policies/oc-qos:scheduler-policy/oc-qos:schedulers/oc-qos:scheduler/oc-qos:two-rate-three-color/oc-qos:config" {
    ext:augment-identifier "saos-qos-2r3c-aug";
    description "Adds saos specific configuration to qos two-rate-three-color config model";
    uses saos-qos-2r3c-config;
  }

  // uniconfig augmentations
  augment "/nt:network-topology/nt:topology/nt:node/ut:configuration/oc-qos:qos/oc-qos:config" {
    description "Adds saos specific configuration to qos config model";
    uses saos-qos-extension-config;
  }

  augment "/nt:network-topology/nt:topology/nt:node/ut:configuration/oc-qos:qos/oc-qos:interfaces/oc-qos:interface/oc-qos:config" {
    description "Adds saos specific configuration to qos config model";
    uses saos-qos-if-extension-config;
  }

  augment "/nt:network-topology/nt:topology/nt:node/ut:configuration/oc-qos:qos/oc-qos:scheduler-policies/oc-qos:scheduler-policy/oc-qos:schedulers/oc-qos:scheduler/oc-qos:config" {
    description "Adds saos specific configuration to qos scheduler config model";
    uses saos-qos-scheduler-config;
  }

  augment "/nt:network-topology/nt:topology/nt:node/ut:configuration/oc-qos:qos/oc-qos:scheduler-policies/oc-qos:scheduler-policy/oc-qos:config" {
    description "Adds saos specific configuration to qos scheduler policy config model";
    uses saos-qos-sc-policy-config;
  }

  augment "/nt:network-topology/nt:topology/nt:node/ut:configuration/oc-qos:qos/oc-qos:scheduler-policies/oc-qos:scheduler-policy/oc-qos:schedulers/oc-qos:scheduler/oc-qos:two-rate-three-color/oc-qos:config" {
    description "Adds saos specific configuration to qos two-rate-three-color config model";
    uses saos-qos-2r3c-config;
  }
}
