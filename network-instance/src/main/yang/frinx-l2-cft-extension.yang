module frinx-l2-cft-extension {

  yang-version "1";

  // namespace
  namespace "http://frinx.openconfig.net/yang/cft/extension";

  prefix "l2-cft-ext";

  // import some basic types
  import frinx-openconfig-network-instance { prefix oc-ni; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig interfaces models,
    containing SAOS specific features.";

  revision "2020-02-20" {
    description
      "Initial release";
    reference "4.2.4";
  }

  grouping l2-cft-extension {
    description
      "Enclosing container for the list of subinterfaces associated with a physical interface";
      container cfts {
        description
          "Container for the list of cft.";

        container config {
          description
            "Configuration parameters for cfts.";

          leaf mode {
            type string;
              description "Name of cft mode";
          }
        }

        list cft {
          key "cftName";

          description "List of cft";

          leaf cftName {
            type leafref {
              path "../config/cftName";
            }
            description "Name of cft";
          }
          container config {
            description "Cft config container";

            leaf cftName {
              type string;
                description "Name of cft profile";
            }
            container ctrl-protocols {
              list ctrl-protocol {
                key "name";
                description "List of protocols";
                leaf name {
                  type enumeration {
                     enum 802.1x {
                      description
                        "802.1x";
                    }
                    enum all-bridges-block {
                      description
                        "all-bridges-block";
                    }
                    enum bridge-rsvd-0B0F {
                      description
                        "bridge-rsvd-0B0F";
                    }
                    enum bridge-rsvd-0C0D {
                      description
                        "bridge-rsvd-0C0D";
                    }
                    enum cisco-cdp {
                      description
                        "cisco-cdp";
                    }
                    enum cisco-dtp {
                      description
                        "cisco-dtp";
                    }
                    enum cisco-pagp {
                      description
                        "cisco-pagp";
                    }
                    enum cisco-pvst {
                      description
                        "cisco-pvst";
                    }
                    enum cisco-stp-uplink-fast {
                      description
                        "cisco-stp-uplink-fast";
                    }
                    enum cisco-udld {
                      description
                        "cisco-udld";
                    }
                    enum cisco-vtp {
                      description
                        "cisco-vtp";
                    }
                    enum elmi {
                      description
                        "elmi";
                    }
                    enum esmc {
                      description
                        "esmc";
                    }
                    enum garp-block {
                      description
                        "garp-block";
                    }
                    enum gmrp {
                      description
                        "gmrp";
                    }
                    enum gvrp {
                      description
                        "gvrp";
                    }
                    enum lacp {
                      description
                        "lacp";
                    }
                    enum lacp-marker {
                      description
                        "lacp-marker";
                    }
                    enum lldp {
                      description
                        "lldp";
                    }
                    enum mef-ce2-bridge-block {
                      description
                        "mef-ce2-bridge-block";
                    }
                    enum oam {
                      description
                        "oam";
                    }
                    enum ptp-peer-delay {
                      description
                        "ptp-peer-delay";
                    }
                    enum vlan-bridge {
                      description
                        "vlan-bridge";
                    }
                    enum xstp {
                      description
                        "xstp";
                    }
                    enum bridge-block {
                      description
                        "bridge-block";
                    }
                  }
                  description "Name of ctrl-protocol";
                }
                leaf disposition {
                  type enumeration {
                    enum discard {
                     description "Discard disposition";
                    }
                    enum forward {
                      description "Forward disposition";
                    }
                    enum egress-l2pttranslate {
                      description "Egress disposition";
                    }
                  }
                 description "Disposition of cft";
              }
            }
          }
        }
      }
    }
  }

  grouping l2-cft-if-extension {
    description "containter for interface config";
    container interface-cft {
      description "interface-cft container";
      leaf profile {
        type string;
        description "Name of cft profile";
      }
      leaf enabled {
        type boolean;
        description "port enable/disable";
      }
    }
  }

  // augment statements
  augment "/oc-ni:network-instances/oc-ni:network-instance/oc-ni:config" {
    description "Adds SAOS specific configuration to network-instance model";
    ext:augment-identifier "l2-cft-ext";
    uses l2-cft-extension;
  }

  augment "/oc-ni:network-instances/oc-ni:network-instance/oc-ni:interfaces/oc-ni:interface/oc-ni:config" {
    description "Adds SAOS specific configuration to network-instance/interface model";
    ext:augment-identifier "l2-cft-if-ext";
    uses l2-cft-if-extension;
  }

  // uniconfig augmentations
  augment "/nt:network-topology/nt:topology/nt:node/ut:configuration/oc-ni:network-instances/oc-ni:network-instance/oc-ni:config" {
    description "Adds SAOS specific configuration to network-instance model";
    uses l2-cft-extension;
  }

  // uniconfig augmentations
  augment "/nt:network-topology/nt:topology/nt:node/ut:configuration/oc-ni:network-instances/oc-ni:network-instance/oc-ni:interfaces/oc-ni:interface/oc-ni:config" {
    description "Adds SAOS specific configuration to network-instance/interface model";
    uses l2-cft-if-extension;
  }
}
