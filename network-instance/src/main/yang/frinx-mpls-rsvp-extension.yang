module frinx-mpls-rsvp-extension {

  yang-version "1";

  // namespace
  namespace "http://frinx.openconfig.net/yang/mpls/extension";

  prefix "mpls-rsvp-ext";

  // import some basic types
  import frinx-openconfig-network-instance { prefix oc-netinst; }
  import frinx-openconfig-network-instance-types { prefix oc-ni-types; }
  import yang-ext { prefix ext; }
  // uniconfig imports
  import network-topology { prefix nt; revision-date "2013-10-21"; }
  import frinx-uniconfig-topology { prefix ut; revision-date "2017-11-21"; }

  // meta
  organization "Frinx s.r.o";

  contact
    "support@frinx.io";

  description
    "Set of augments needed to OpenConfig mpls models,
    containing additional features.";

  revision "2017-10-24" {
    description
      "Initial release";
    reference "3.1.1";
  }

  // grouping statements

  grouping mpls-rsvp-subscription-config {
    description
      "Additional configuration data for MPLS RSVP subscription";

    leaf bandwidth {
      type union {
        type uint32 {
            range "0..4294967295";
        }
        type string {
            pattern "default";
        }
      }

      units "bps";

      description
        "Total reservable bandwidth";
    }
  }

  // augment statements

  augment "/oc-netinst:network-instances/oc-netinst:network-instance/oc-netinst:mpls/oc-netinst:signaling-protocols/oc-netinst:rsvp-te/oc-netinst:interface-attributes/oc-netinst:interface/oc-netinst:subscription/oc-netinst:config" {
    when "oc-netinst:type = 'oc-ni-types:DEFAULT_INSTANCE'" {
      description "Active when the network-instance is a DEFAULT_INSTANCE";
    }
    ext:augment-identifier "ni-mpls-rsvp-if-subscrip-aug";
    description "Adds additional MPLS RSVP settings to subscription on individual";

    uses mpls-rsvp-subscription-config;
  }

  // uniconfig augmentations

  augment "/nt:network-topology/nt:topology/nt:node/ut:configuration/oc-netinst:network-instances/oc-netinst:network-instance/oc-netinst:mpls/oc-netinst:signaling-protocols/oc-netinst:rsvp-te/oc-netinst:interface-attributes/oc-netinst:interface/oc-netinst:subscription/oc-netinst:config" {
    when "oc-netinst:type = 'oc-ni-types:DEFAULT_INSTANCE'" {
      description "Active when the network-instance is a DEFAULT_INSTANCE";
    }
    description "Adds additional MPLS RSVP settings to subscription on individual";

    uses mpls-rsvp-subscription-config;
  }

}
