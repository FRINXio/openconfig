module frinx-juniper-pf-interfaces-extension {

  yang-version "1";

  // namespace
  namespace "http://frinx.openconfig.net/yang/network-instance/pf-interfaces-extension/juniper";

  prefix "juniper-pf-if-ext";

  // import some basic types
  import frinx-openconfig-network-instance { prefix oc-netinst; }
  import frinx-openconfig-network-instance-types { prefix oc-ni-types; }
  import yang-ext { prefix ext; }
  // uniconfig imports
  import network-topology { prefix nt; revision-date "2013-10-21"; }
  import frinx-uniconfig-topology { prefix ut; revision-date "2017-11-21"; }

  // meta
  organization "Frinx s.r.o";

  contact
    "support@frinx.io";

  description
    "Extended interface parameters with Juniper specific in policy-forwarding";

  revision "2017-11-09" {
    description
      "Initial release";
    reference "3.1.1";
  }

  // grouping statements

  grouping juniper-pf-interface-extension-config {
    description
      "Extended configuration parameters relating to an interface to policy
      forwarding rule binding.";

    leaf scheduler-map {
      description "Output scheduler map";
      type string;
    }

    container classifiers {
      description "Classify incoming packets based on code point value";

      container exp {
        description "MPLS EXP classifier";

        leaf name {
          description "Classifier name";
          type string;
        }
      }

      container inet-precedence {
        description "IPv4 precedence classifier";

        leaf name {
          description "Classifier name";
          type string;
        }
      }
    }
  }

  // augment statements

  augment "/oc-netinst:network-instances/oc-netinst:network-instance/oc-netinst:policy-forwarding/oc-netinst:interfaces/oc-netinst:interface/oc-netinst:config" {
    when "oc-netinst:type = 'oc-ni-types:DEFAULT_INSTANCE'" {
      description "Active when the network-instance is a DEFAULT_INSTANCE";
    }
    ext:augment-identifier "ni-pf-if-juniper-aug";
    description "Adds extended interface settings to policy-forwarding";

    uses juniper-pf-interface-extension-config;
  }

  // uniconfig augmentations

  augment "/nt:network-topology/nt:topology/nt:node/ut:configuration/oc-netinst:network-instances/oc-netinst:network-instance/oc-netinst:policy-forwarding/oc-netinst:interfaces/oc-netinst:interface/oc-netinst:config" {
    when "oc-netinst:type = 'oc-ni-types:DEFAULT_INSTANCE'" {
      description "Active when the network-instance is a DEFAULT_INSTANCE";
    }
    description "Adds extended interface settings to policy-forwarding";

    uses juniper-pf-interface-extension-config;
  }

}
