module frinx-saos-ra-extension {

  yang-version "1";

  // namespace
  namespace "http://frinx.openconfig.net/yang/saos/extension";

  prefix "saos-ra-ext";

  // import some basic types
  import frinx-openconfig-network-instance { prefix oc-ni; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig network-instance models,
    containing SAOS specific features.";

  revision "2022-06-26" {
    description
      "Initial release";
    reference "4.2.4";
  }

  grouping saos-ra-extension {
    container relay-agent {
      container config {
        leaf enable {
          type boolean;
          description "Enable/disable dhcp l2-relay agent for virtual-switch";
        }
      }
    }
  }

  // augment statements
  augment "/oc-ni:network-instances/oc-ni:network-instance" {
    description "Adds SAOS specific configuration to network-instance model";
    ext:augment-identifier "ra-saos-aug";
    uses saos-ra-extension;
  }

  // uniconfig augmentations
  augment "/nt:network-topology/nt:topology/nt:node/ut:configuration/oc-ni:network-instances/oc-ni:network-instance" {
    description "Adds SAOS specific configuration to network-instance model";
    uses saos-ra-extension;
  }
}
