module frinx-ospf-extension {

  yang-version "1";

  // namespace
  namespace "http://frinx.openconfig.net/yang/ospf/extension";

  prefix "ospf-ext";

  // import some basic types
  import frinx-openconfig-network-instance { prefix oc-ni; }
  import frinx-openconfig-routing-policy { prefix oc-rpol; revision-date 2017-07-14; }
  import yang-ext { prefix ext; }

  // uniconfig imports
  import network-topology { prefix nt; revision-date "2013-10-21"; }
  import frinx-uniconfig-topology { prefix ut; revision-date "2017-11-21"; }

  // meta
  organization "Frinx s.r.o";

  contact
    "support@frinx.io";

  revision "2019-01-17" {
    description
      "Initial release";
  }

  grouping ospf-area-interface-ext-config {
    leaf enabled {
      type boolean;
    }
  }

  grouping protocol-config {
    leaf-list export-policy {
      type leafref {
        path "/oc-rpol:routing-policy/oc-rpol:policy-definitions/" +
            "oc-rpol:policy-definition/oc-rpol:name";
      }
      description
        "Name of policy which needs to be exported.";
    }
  }

  // network-instances augmentations
  augment "/oc-ni:network-instances/oc-ni:network-instance/oc-ni:protocols/oc-ni:protocol/oc-ni:ospfv2/" +
  "oc-ni:areas/oc-ni:area/oc-ni:interfaces/oc-ni:interface/oc-ni:config" {
    ext:augment-identifier "ospf-area-if-conf-aug";
    description "Extends settings on the OSPFv2 area interface";

    uses ospf-ext:ospf-area-interface-ext-config;
  }

  augment "/oc-ni:network-instances/oc-ni:network-instance/oc-ni:protocols/oc-ni:protocol/oc-ni:config" {
    description "Extends protocol/config with export-policy of ospf";
    ext:augment-identifier "protocol-conf-aug";
    uses protocol-config;
  }

  // uniconfig augmentations
  augment "/nt:network-topology/nt:topology/nt:node/ut:configuration/oc-ni:network-instances/oc-ni:network-instance/" +
  "oc-ni:protocols/oc-ni:protocol/oc-ni:ospfv2/oc-ni:areas/oc-ni:area/oc-ni:interfaces/oc-ni:interface/oc-ni:config" {
    description "Extends settings on the OSPFv2 area interface";

    uses ospf-ext:ospf-area-interface-ext-config;
  }

  augment "/nt:network-topology/nt:topology/nt:node/ut:configuration/" +
  "oc-ni:network-instances/oc-ni:network-instance/oc-ni:protocols/oc-ni:protocol/oc-ni:config" {
    description "Extends protocol/config with export-policy of ospf";

    uses protocol-config;
  }
}
