module frinx-brocade-pf-interfaces-extension {

  yang-version "1";

  // namespace
  namespace "http://frinx.openconfig.net/yang/network-instance/pf-interfaces-extension/brocade";

  prefix "brocade-pf-if-ext";

  // import some basic types
  import frinx-openconfig-network-instance { prefix oc-netinst; }
  import yang-ext { prefix ext; }
  // uniconfig imports
  import network-topology { prefix nt; revision-date "2013-10-21"; }
  import frinx-openconfig-network-instance-types { prefix oc-ni-types; }
  import frinx-uniconfig-topology { prefix ut; revision-date "2017-11-21"; }

  // meta
  organization "Frinx s.r.o";

  contact
    "support@frinx.io";

  description
    "Extended interface parameters with BROCADE specific in policy-forwarding";

  revision "2019-07-26" {
    description
      "Initial release";
    reference "3.1.1";
  }

  // grouping statements

  grouping brocade-pf-interface-extension-config {
    description
      "Extended configuration parameters relating to an interface to policy
      forwarding rule binding.";

    leaf input-service-policy {
      description
            "Service policy which is applied on packets in ingress direction";

      type string;
    }
    leaf output-service-policy {
      description
            "Service policy which is applied on packets in egress direction";

      type string;
    }
  }

  // augment statements

  augment "/oc-netinst:network-instances/oc-netinst:network-instance/oc-netinst:policy-forwarding/oc-netinst:interfaces/oc-netinst:interface/oc-netinst:config" {
    when "oc-netinst:type = 'oc-ni-types:DEFAULT_INSTANCE'" {
      description "Active when the network-instance is a DEFAULT_INSTANCE";
    }
    ext:augment-identifier "ni-pf-if-brocade-aug";
    description "Adds extended interface settings to policy-forwarding";

    uses brocade-pf-interface-extension-config;
  }

  // uniconfig augmentations

  augment "/nt:network-topology/nt:topology/nt:node/ut:configuration/oc-netinst:network-instances/oc-netinst:network-instance/oc-netinst:policy-forwarding/oc-netinst:interfaces/oc-netinst:interface/oc-netinst:config" {
    when "oc-netinst:type = 'oc-ni-types:DEFAULT_INSTANCE'" {
      description "Active when the network-instance is a DEFAULT_INSTANCE";
    }
    description "Adds extended interface settings to policy-forwarding";

    uses brocade-pf-interface-extension-config;
  }

}
