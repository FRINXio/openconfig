module frinx-brocade-cp-extension {

  yang-version "1";

  // namespace
  namespace "http://frinx.openconfig.net/yang/network-instance/cp-extension/brocade";

  prefix "brocade-cp-ext";

  // import some basic types
  import frinx-openconfig-network-instance { prefix oc-netinst; }
  import yang-ext { prefix ext; }
  // uniconfig imports
  import network-topology { prefix nt; revision-date "2013-10-21"; }
  import frinx-openconfig-network-instance-types { prefix oc-ni-types; }
  import frinx-uniconfig-topology { prefix ut; revision-date "2017-11-21"; }

  // meta
  organization "Frinx s.r.o";

  contact
    "support@frinx.io";

  description
    "Extended connection-point local parameters to allow for untagged vlan endpoints";

  revision "2019-08-12" {
    description
      "Initial release";
    reference "3.1.1";
  }

  // augment statements

  grouping brocade-cp-extension-local {
    leaf subinterface-untagged {
      type boolean;
    }
  }

  augment "/oc-netinst:network-instances/oc-netinst:network-instance/oc-netinst:connection-points/oc-netinst:connection-point/oc-netinst:endpoints/oc-netinst:endpoint/oc-netinst:local/oc-netinst:config" {
    ext:augment-identifier "ni-cp-brocade-aug";
    description "Adds untagged subinterface setting";

    uses brocade-cp-extension-local;
  }

  // uniconfig augmentations

  augment "/nt:network-topology/nt:topology/nt:node/ut:configuration/oc-netinst:network-instances/oc-netinst:network-instance/oc-netinst:connection-points/oc-netinst:connection-point/oc-netinst:endpoints/oc-netinst:endpoint/oc-netinst:local/oc-netinst:config" {
    description "Adds untagged subinterface setting";

    uses brocade-cp-extension-local;
  }

}
