module frinx-cisco-mpls-te-extension {

  yang-version "1";

  // namespace
  namespace "http://frinx.openconfig.net/yang/mpls/cisco";

  prefix "cisco-mpls-te-ext";

  // import some basic types
  import frinx-openconfig-network-instance { prefix oc-netinst; }
  import frinx-openconfig-network-instance-types { prefix oc-ni-types; }
  import yang-ext { prefix ext; }
  // uniconfig imports
  import network-topology { prefix nt; revision-date "2013-10-21"; }
  import frinx-uniconfig-topology { prefix ut; revision-date "2017-11-21"; }

  // meta
  organization "Frinx s.r.o";

  contact
    "support@frinx.io";

  description
    "Set of augments needed to OpenConfig mpls models,
    containing CISCO specific features.";

  revision "2017-10-24" {
    description
      "Initial release";
    reference "3.1.1";
  }

  // grouping statements

  grouping cisco-mpls-te-tunnel-config {
    description
      "Configuration data for each CISCO MPLS TE tunnel";

    leaf load-share {
      type uint32 {
        range "1..4294967295";
      }

      units "Kbps";

      description
        "Determines load-sharing balancing parameters for a specified tunnel";
    }
  }

  grouping cisco-mpls-te-tunnel-state {
    description
      "CISCO MPLS TE tunnel related operational state";

    //TODO: placeholder for operational state
  }

  grouping cisco-mpls-te-tunnel-top {
    description
      "Top-level grouping for CISCO MPLS TE tunnel data";

    container cisco-mpls-te-extension {
      description
        "Enclosing container for CISCO MPLS TE tunnel specific data.";

      container config {
          description "Configuration parameters for CISCO MPLS TE tunnel";

          uses cisco-mpls-te-tunnel-config;
      }

      container state {

        config false;
        description "State variables for CISCO MPLS TE tunnel";

        uses cisco-mpls-te-tunnel-config;
        uses cisco-mpls-te-tunnel-state;
      }
    }
  }

  grouping cisco-mpls-te-global-config {
    description
      "Configuration data for MPLS TE";

    container config {
      leaf enabled {
        type boolean;
        description "Enables/disables traffic-eng on the device.";
      }
    }
  }

  // augment statements

  augment "/oc-netinst:network-instances/oc-netinst:network-instance/oc-netinst:mpls/oc-netinst:lsps/oc-netinst:constrained-path/oc-netinst:tunnels/oc-netinst:tunnel" {
    when "oc-netinst:type = 'oc-ni-types:DEFAULT_INSTANCE'" {
      description "Active when the network-instance is a DEFAULT_INSTANCE";
    }
    ext:augment-identifier "ni-mpls-te-tunnel-cisco-aug";
    description "Adds CISCO MPLS TE tunnel settings to individual tunnel
    interfaces";

    uses cisco-mpls-te-tunnel-top;
  }

  augment "/oc-netinst:network-instances/oc-netinst:network-instance/oc-netinst:mpls/oc-netinst:te-global-attributes" {
      when "oc-netinst:type = 'oc-ni-types:DEFAULT_INSTANCE'" {
        description "Active when the network-instance is a DEFAULT_INSTANCE";
      }
      ext:augment-identifier "ni-mpls-te-enabled-cisco-aug";
      description "Adds MPLS TE enabled flag";

      uses cisco-mpls-te-global-config;
    }

  // uniconfig augmentations

  augment "/nt:network-topology/nt:topology/nt:node/ut:configuration/oc-netinst:network-instances/oc-netinst:network-instance/oc-netinst:mpls/oc-netinst:lsps/oc-netinst:constrained-path/oc-netinst:tunnels/oc-netinst:tunnel" {
    when "oc-netinst:type = 'oc-ni-types:DEFAULT_INSTANCE'" {
      description "Active when the network-instance is a DEFAULT_INSTANCE";
    }
    description "Adds CISCO MPLS TE tunnel settings to individual tunnel
    interfaces";

    uses cisco-mpls-te-tunnel-top;
  }

  augment "/nt:network-topology/nt:topology/nt:node/ut:configuration/oc-netinst:network-instances/oc-netinst:network-instance/oc-netinst:mpls/oc-netinst:te-global-attributes" {
    when "oc-netinst:type = 'oc-ni-types:DEFAULT_INSTANCE'" {
      description "Active when the network-instance is a DEFAULT_INSTANCE";
    }
    description "Adds MPLS TE enabled flag";

    uses cisco-mpls-te-global-config;
  }

}
