module frinx-cisco-ospf-extension {

  yang-version "1";

  // namespace
  namespace "http://frinx.openconfig.net/yang/ospf/cisco";

  prefix "cisco-ospf-ext";

  // import some basic types
  import frinx-openconfig-ospf-types { prefix oc-ospf-types; }

  // meta
  organization "Frinx s.r.o";

  contact
    "support@frinx.io";

  description
    "Set of augments needed to OpenConfig OSPF models,
    containing CISCO specific features.";

  revision "2017-11-24" {
    description
      "Initial release";
    reference "3.1.1";
  }

  identity MAX_METRIC_SUMMARY_LSA {
    base "oc-ospf-types:MAX_METRIC_INCLUDE";
    description
      "Maps to 'summary-lsa'";
  }

  identity MAX_METRIC_ON_SWITCHOVER {
    base "oc-ospf-types:MAX_METRIC_TRIGGER";
    description
      "Set the maximum metric on switchover. Maps to on-switchover";
  }
}
