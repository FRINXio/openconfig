module frinx-openconfig-probes-types {

  yang-version "1";

  // namespace
  namespace "http://frinx.openconfig.net/yang/probes/types";

  prefix "oc-probes-types";

  // import some basic types
  import frinx-openconfig-extensions { prefix oc-ext; }

  // meta
  organization "OpenConfig working group";

  contact
    "OpenConfig working group
    www.openconfig.net";

  description
    "This module defines types related to the probes.";

  oc-ext:openconfig-version "1.1.0";

  revision "2017-09-05" {
    description
      "Initial public revision";
    reference "0.1.0";
  }

  typedef test-type {
    type enumeration {
      enum ICMP {
        description
          "Send ICMP echo requests.";
      }
      enum ICMP6 {
        description
          "Send ICMP6 echo requests.";
      }
      enum ICMP_TIMESTAMP {
        description
          "Send ICMP timestamp requests.";
      }
      enum ICMP6_TIMESTAMP {
        description
          "Sedn ICMP6 timestamp requests.";
      }
      enum TCP {
        description
          "Send TPC packets.";
      }
      enum UDP {
        description
          "Send UDP packets.";
      }
      enum UDP_TIMESTAMP {
        description
          "Send UDP packets with timestamp.";
      }
      enum HTTP_GET {
        description
          "Execute HTTP GET requests.";
      }
      enum HTTP_GET_META {
        description
          "Execute HTTP GET requests of metadata.";
      }
    }
    description
      "Type definition with enumerations describing the basis of
      the probe test type identifier";
  }

}
