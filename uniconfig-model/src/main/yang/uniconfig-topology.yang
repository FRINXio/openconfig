module uniconfig-topology {

  yang-version 1;
  namespace "http://frinx.io/yang/uniconfig-topology";
  prefix "ut";

  import network-topology { prefix nt; revision-date 2013-10-21; }
  import yang-ext { prefix ext; revision-date "2013-07-09";}

  revision "2017-11-21" {
    description "Initial revision";
  }

  augment "/nt:network-topology/nt:topology/nt:topology-types" {
    ext:augment-identifier "uniconfig-topology";
    container uniconfig {
    }
  }

  augment "/nt:network-topology/nt:topology/nt:node" {
    when "/nt:network-topology/nt:topology/nt:topology-types/ut:uniconfig";
    ext:augment-identifier "uniconfig-node-aug";
    container configuration {
      description
        "Target element for augmentations with OpenConfig configuration";
    }
  }

}
