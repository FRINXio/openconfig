module frinx-uniconfig-topology {

  yang-version 1;
  namespace "http://frinx.openconfig.net/yang/uniconfig-topology";
  prefix "ut";

  import network-topology { prefix nt; revision-date 2013-10-21; }
  import yang-ext { prefix ext; revision-date "2013-07-09";}

  revision "2017-11-21" {
    description "Initial revision";
  }

  grouping uniconfig-node-status {
    leaf connection-status {
      config false;
      type enumeration {
        enum installing {
          description
            "Creation of Unified or Uniconfig mountpoint including initial sync-from-network task.";
        }
        enum installed {
          description
            "Uniconfig mountpoint has been successfully created.";
        }
        enum failed {
          description
            "An error occurred during creation of Unified or Uniconfig mountpoint.";
        }
      }
      description
        "Status of Uniconfig mountpoint.";
    }

    leaf status-message {
      config false;
      type string;
      description
        "Description of Uniconfig node status/reason of failure.";
    }
  }

  augment "/nt:network-topology/nt:topology/nt:topology-types" {
    ext:augment-identifier "uniconfig-topology";
    container uniconfig {
    }
  }

  augment "/nt:network-topology/nt:topology/nt:node" {
    when "/nt:network-topology/nt:topology/nt:topology-types/ut:uniconfig";
    ext:augment-identifier "uniconfig-node-aug";
    container configuration {
      description
        "Target element for augmentations from OpenConfig configuration";
    }
    uses uniconfig-node-status;
  }
}
