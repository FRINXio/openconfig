module frinx-event-types {

  yang-version "1";

  // namespace
  namespace "http://frinx.openconfig.net/yang/event-types";

  prefix "event-types";

  // import some basic types

  // meta
  organization "Frinx s.r.o";

  contact
    "support@frinx.io";

  description
    "Event types";

  revision "2017-10-24" {
    description
      "Initial release";
    reference "3.1.1";
  }

  // identity statements
  identity EVENT_TYPE {
  	description
    "A base identity which can be extended to indicate different
    types of events supported by a device.";
  }

  identity LINK_UP_DOWN {
    base EVENT_TYPE;
    description
      "Link status event generated for link UP and DOWN changes.";
  }
}
