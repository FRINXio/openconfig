module frinx-cisco-routing-policy-extension {

  yang-version "1";

  // namespace
  namespace "http://frinx.openconfig.net/yang/routing-policy/cisco";

  prefix "cisco-rpol-ext";

  // import some basic types
  import frinx-openconfig-routing-policy { prefix "oc-rpol";}

  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig routing-policy models,
    containing CISCO specific features.";

  revision "2021-04-22" {
    description
      "Initial release";
    reference "4.2.7";
  }

  // Route map set operation type

  identity SET_OPERATION {
    description
      "Value for route map to permit/deny set operations.";
  }

  identity PERMIT {
    base SET_OPERATION;
    description
      "Route map permits set operations";
  }

  identity DENY {
    base SET_OPERATION;
    description
      "Route map denies set operations";
  }

  // grouping statements

  grouping cisco-prefix-config-extension {
    leaf sequence-id {
      type uint32;
      description
        "Unique sequence number for the policy rule.";
    }

    leaf operation {
      type identityref {
        base SET_OPERATION;
      }
      description
        "Specifies the forwarding operation. Operation
          must be specified for each prefix-list entry";
    }

    leaf minimum-prefix-length {
      type uint8 {
        range "0 .. 128";
      }
      description
        "Minimum prefix length to be matched";
    }

    leaf maximum-prefix-length {
      type uint8 {
        range "0 .. 128";
      }
      description
        "Maximum prefix length to be matched";
    }
  }

  grouping cisco-rpol-extension-config {
    description
      "Match values from routing table";

    leaf set-operation {
      type identityref {
        base SET_OPERATION;
      }
      description
        "Value for route map to permit/deny set operations.";
    }
  }

  // augment statements

  augment "/oc-rpol:routing-policy/oc-rpol:policy-definitions/oc-rpol:policy-definition/oc-rpol:statements" +
    "/oc-rpol:statement/oc-rpol:config" {
    ext:augment-identifier "prefix-list-aug";
    description "Adds Cisco specific configuration to routing policy model";

    uses cisco-rpol-extension-config;
  }

  augment "/oc-rpol:routing-policy/oc-rpol:defined-sets/oc-rpol:prefix-sets/oc-rpol:prefix-set/oc-rpol:prefixes" +
        "/oc-rpol:prefix/oc-rpol:config" {
    ext:augment-identifier "prefix-config-aug";
    description "Adds Cisco specific configuration to
                prefix model";

    uses cisco-prefix-config-extension;
  }

  // uniconfig augmentations

  augment "/nt:network-topology/nt:topology/nt:node/ut:configuration/oc-rpol:routing-policy/oc-rpol:policy-definitions" +
    "/oc-rpol:policy-definition/oc-rpol:statements/oc-rpol:statement/oc-rpol:config" {
    description "Adds Cisco specific configuration to routing policy model";

    uses cisco-rpol-extension-config;
  }

  augment "/nt:network-topology/nt:topology/nt:node/ut:configuration/oc-rpol:routing-policy/oc-rpol:defined-sets" +
        "/oc-rpol:prefix-sets/oc-rpol:prefix-set/oc-rpol:prefixes/oc-rpol:prefix/oc-rpol:config" {
    description "Adds Cisco specific statistics configuration to
                routing policy model";

    uses cisco-prefix-config-extension;
  }
}
