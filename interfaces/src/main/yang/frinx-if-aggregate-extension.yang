module frinx-if-aggregate-extension {

  yang-version "1";

  // namespace
  namespace "http://frinx.openconfig.net/yang/interfaces/aggregate-ext";

  prefix "if-lag-ext";

  // import some basic types
  import frinx-openconfig-interfaces { prefix oc-if; }
  import frinx-openconfig-if-aggregate { prefix oc-lag; }
  import frinx-openconfig-if-ethernet { prefix oc-eth; }
  import iana-if-type { prefix ift; }
  import ietf-yang-types { prefix yang; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig interfaces models,
    containing LAG specific features.";

  revision "2018-09-26" {
    description
      "Initial release";
    reference "3.1.7";
  }

  // grouping statements

  grouping if-aggregate-extentions-config {
    leaf admin-key {
      type uint16;
      description
        "Member port of LACP has key value. All member ports in one aggregator have same key
        values. To make the aggregator consisted of specified member ports, configure the
        different key value with the key value of another port.";
    }
  }

  grouping if-aggregate-address-config {
    leaf mac-address {
      type yang:mac-address;
      description
        "Assigns a MAC address to the Ethernet interface.  If not
        specified, the corresponding operational state leaf is
        expected to show the system-assigned MAC address.";
    }

    leaf system-id-mac {
      type yang:mac-address;
      description
        "The MAC address portion of the node's System ID. This is
        combined with the system priority to construct the 8-octet
        system-id";
    }
  }

  // augment statements

  augment "/oc-if:interfaces/oc-if:interface/oc-eth:ethernet/" +
    "oc-eth:config" {
    when "oc-if:type = 'ift:ethernetCsmacd'" {
      description "active when the interface is Ethernet";
    }
    description "Adds LAG specific configuration to individual Ethernet interfaces";

    uses if-aggregate-extentions-config;
  }

  augment "/oc-if:interfaces/oc-if:interface/oc-eth:ethernet/" +
    "oc-eth:state" {
    when "oc-if:type = 'ift:ethernetCsmacd'" {
      description "active when the interface is Ethernet";
    }
    description "Adds LAG specific configuration to individual Ethernet interfaces";

    uses if-aggregate-extentions-config;
  }

  augment "/oc-if:interfaces/oc-if:interface/oc-lag:aggregation/oc-lag:config" {
    when "oc-if:type = 'ift:ieee8023adLag'" {
      description "Active when the interface is a LAG";
    }
    ext:augment-identifier "if-lag-aug";
    description "Adds additional Juniper specific settings to a LAG interface";

    uses if-aggregate-address-config;
  }

  // uniconfig augmentations

  augment "/nt:network-topology/nt:topology/nt:node/ut:configuration/oc-if:interfaces/oc-if:interface/" +
    "oc-eth:ethernet/oc-eth:config" {
    when "oc-if:type = 'ift:ethernetCsmacd'" {
      description "active when the interface is Ethernet";
    }
    description "Adds LAG specific configuration to individual Ethernet interfaces";

    uses if-aggregate-extentions-config;
  }

  augment "/nt:network-topology/nt:topology/nt:node/ut:configuration/oc-if:interfaces/oc-if:interface/" +
    "oc-eth:ethernet/oc-eth:state" {
    when "oc-if:type = 'ift:ethernetCsmacd'" {
      description "active when the interface is Ethernet";
    }
    description "Adds LAG specific configuration to individual Ethernet interfaces";

    uses if-aggregate-extentions-config;
  }

  augment "/nt:network-topology/nt:topology/nt:node/ut:configuration/oc-if:interfaces/oc-if:interface/oc-lag:aggregation/oc-lag:config" {
    when "oc-if:type = 'ift:ieee8023adLag'" {
     description "Active when the interface is a LAG";
    }
    description "Adds additional Juniper specific settings to a LAG interface";

    uses if-aggregate-address-config;
  }
}
