module frinx-cisco-if-extension {

  yang-version "1";

  // namespace
  namespace "http://frinx.openconfig.net/yang/interfaces/cisco";

  prefix "cisco-if-ext";

  // import some basic types
  import frinx-openconfig-interfaces { prefix oc-if; }
  import frinx-openconfig-if-ethernet { prefix oc-eth; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig interfaces models,
    containing CISCO specific features.";

  revision "2017-10-24" {
    description
      "Initial release";
    reference "3.1.1";
  }

  // grouping statements

  grouping cisco-if-extension-config {

    leaf port-type {
      type enumeration {
        enum eni {
          description
            "ENI port-type";
        }
        enum nni {
          description
            "NNI port-type";
        }
        enum uni {
          description
            "UNI port-type";
        }
      }
    }

    leaf snmp-trap-link-status {
      type boolean;
      description
        "Allow SNMP LINKUP and LINKDOWN traps";
    }

    leaf switchport-mode {
      type enumeration {
        enum trunk {
          description
            "Set trunking mode to TRUNK unconditionally";
        }
        enum access {
          description
            "Set trunking mode to ACCESS unconditionally";
        }
        enum dot1q-tunnel {
          description
            "Set trunking mode to TUNNEL unconditionally";
        }
      }
    }

    leaf switchport-access-vlan {
      type uint32 {
        range "1..4094";
      }
      description
        "VLAN ID of the VLAN when this port is in access mode";
    }

    leaf-list switchport-trunk-allowed-vlan-add {
      type uint32 {
        range "1 .. 4094";
      }
      description
        "VLAN IDs of the allowed VLANs when this port is in trunking mode";
    }

    leaf switchport-port_security-enable {
      type boolean;
      description
        "Enables port security on the interface.";
    }

    leaf switchport-port_security-maximum {
      type uint32 {
        range "1 .. 3072";
      }
      description
        "Sets the maximum number of secure MAC addresses for the interface.";
    }

    leaf switchport-port_security-violation {
      type enumeration {
        enum protect {
          description
            "Drops packets with unknown source addresses until you remove a sufficient
             number of secure MAC addresses to drop below the maximum value.";
        }
        enum restrict {
          description
            "Drops packets with unknown source addresses until you remove a sufficient
             number of secure MAC addresses to drop below the maximum value and causes
             the SecurityViolation counter to increment.";
        }
        enum shutdown {
          description
            "Puts the interface into the error-disabled state immediately and sends
             an SNMP trap notification.";
        }
      }
    }

    leaf switchport-port_security-aging-time {
      type uint32 {
        range "1 .. 1440";
      }
      description
        "Configures the secure MAC address aging time on the port.
         The aging_time range is 1 to 1440 minutes (default is 0).";
    }

    leaf switchport-port_security-aging-type {
      type enumeration {
        enum absolute {
          description
            "Absolute aging(default)";
        }
        enum inactivity {
          description
            "Aging based on inactivity time period.";
        }
      }
    }

    leaf switchport-port_security-aging-static {
      type boolean;
      description
        "Enable aging for configured secure addresses.";
    }

    leaf ip-redirects {
      type boolean;
      description
        "Enable sending ICMP Redirect messages";
    }

    leaf ip-unreachables {
      type boolean;
      description
        "Enable sending ICMP Unreachable messages";
    }

    leaf ip-proxy-arp {
      type boolean;
      description
        "Enable proxy ARP";
    }

    leaf ipv6-nd-ra-suppress {
      type string;
      description
        "Enable IPv6 interface subcommands.";
    }

    leaf-list l2-protocols {
      type string;
      description
        "Entries for tunnel Layer2 protocols";
    }

    leaf lldp-transmit {
      type boolean;
      description
        "Enable LLDP transmission on interface";
    }

    leaf lldp-receive {
      type boolean;
      description
        "Enable LLDP reception on interface";
    }

    leaf negotiation-auto {
      type boolean;
      description
        "Select autonegotiation mode";
    }

    leaf cdp-enable {
      type boolean;
      description
        "Enable CDP on interface";
    }

    leaf fhrp-minimum-delay {
      type uint16 {
        range "0 .. 3600";
      }
      units seconds;
      description
        "FHRP minimum delay timer";
    }

    leaf fhrp-reload-delay {
      type uint16 {
        range "0 .. 3600";
      }
      units seconds;
      description
        "FHRP reload delay timer";
    }

    leaf vrf-forwarding {
      type string;
      description
        "Configure forwarding table";
    }

    uses service-policy;
    uses storm-control;
    uses hold-queue;
  }

  grouping hold-queue {

    description "Grouping for hold-queue statement values set to interfaces.";
    container hold-queue {
      leaf in {
        type uint32 {
          range "0 .. 240000";
        }
        description "Value for input queue.";
      }

      leaf out {
        type uint32 {
          range "0 .. 240000";
        }
        description "Value for output queue.";
      }
    }
  }

  // service-policy was moved to qos-interfaces
  grouping service-policy {
    container service-policy {
      leaf input {
        type string;
        description
          "Assign policy-map to the input of an interface";
      }

      leaf output {
        type string;
        description
          "Assign policy-map to the output of an interface";
      }
    }
  }

  grouping storm-control {
    list storm-control {
      key "address";
      ordered-by user;

      leaf address {
        type enumeration {
          enum broadcast {
            description
              "Broadcast address storm control";
          }
          enum multicast {
            description
              "Multicast address storm control";
          }
          enum unicast {
            description
              "Unicast address storm control";
          }
        }
        mandatory true;
      }

      leaf level {
        type decimal64 {
          fraction-digits 2;
          range "0 .. 100";
        }
        mandatory true;
        description
          "Rising threshold level (percentage)";
      }
    }
  }

  grouping cisco-if-eth-extension-config {

    leaf lacp-rate {
      type enumeration {
        enum FAST {
          description
            "Request LACP packets to be ingressed at the
            1 second rate for this interface.";
        }
        enum NORMAL {
          description
            "Request LACP packets to be ingressed the
            30 second rate once the link is estabilished.";
        }
      }
      description "Type of LACP rate mode.";
    }

    leaf lacp-port-priority {
      type uint16 {
        range "0..65535";
      }
      description "Port priority value.";
    }
  }

  grouping service-instance-top {
    description
      "Top-level grouping for service instance data";

    container service-instances {
      description
        "Enclosing container for service instances";

      list service-instance {
        key "id";
        description
          "List of service instances";

        leaf id {
          type leafref {
            path "../config/id";
          }
          description
            "Reference to service instance identifier";
        }

        container config {
          description
            "Configuration data for service instance";

          uses service-instance-config;
        }

        container encapsulation {
          description
            "Encapsulation data for service instance";

          uses service-instance-encapsulation;
        }

        container l2protocols {
          description
            "L2 protocol data for service instance";

          uses service-instance-l2protocols;
        }

        container bridge-domain {
          description
            "Bridge domain data for service instance";

          uses service-instance-bridge-domain;
        }

        container rewrite {
          description
            "Configure ethernet rewrite criteria";

          uses service-instance-rewrite;
        }
      }
    }
  }

  grouping service-instance-config {
    leaf id {
      type uint32 {
        range "1 .. 4000";
      }
      description
        "Service instance identifier";
    }

    leaf trunk {
      type boolean;
      description
        "Flag whether service instance is trunk";
    }

    leaf evc {
      type string;
      description
        "EVC attached to the service instance";
    }
  }

  grouping service-instance-encapsulation {
    leaf untagged {
      type boolean;
      description
        "Untagged encapsulation";
    }

    leaf-list dot1q {
      type string;
      description
        "Dot1q encapsulation VLAN IDs";
    }
  }

  grouping service-instance-l2protocols {
    container service-instance-l2protocol {
      list l2protocol {
        key "name";
        description
          "List of l2protocols";

        leaf name {
          type leafref {
            path "../config/name";
          }
        }
        container config {
          description "";
          uses l2protocol-config;
        }
      }
    }
  }

  grouping l2protocol-config {
    leaf name {
      type string;
      description
        "L2 procol config";
    }
    leaf protocol-type {
      description "Defines a protocol type of l2protocol";
      type enumeration {
        enum tunnel {
          description
            "tunnel L2 control protocol packets as data";
        }
        enum peer {
          description
            "peer L2 control protocol packets as data";
        }
        enum forward {
          description
            "forward L2 control protocol packets as data";
        }
      }
    }
    leaf-list protocol {
      description "Concrete protocol for l2protocol and its type";
      type enumeration {
        enum cdp {
          description
            "Cisco Discovery Protocol";
        }
        enum vtp {
          description
            "Vlan Trunking Protocol";
        }
        enum lacp {
          description
           "LACP Protocol";
        }
        enum lldp {
          description
            "Link Layer Discovery Protocol";
        }
        enum mmrp {
          description
            "Multiple MAC Registration Protocol";
        }
        enum mvrp {
          description
            "Multiple VLAN Registration Protocol";
        }
        enum stp {
          description
            "Spanning Tree Protocol";
        }
        enum elmi {
          description
            "ELMI Protocol";
        }
        enum pagp {
          description
            "Port Aggregation Protocol";
        }
        enum udld {
          description
            "UDLD Protocol";
        }
        enum ptppd {
          description
            "PTP Peer Delay Protocol";
        }
        enum RB {
          description
            "Reserved Protocol using DA Mac 0180.C200.000B";
        }
        enum RC {
          description
            "Reserved Protocol using DA Mac 0180.C200.000C";
        }
        enum RD {
          description
            "Reserved Protocol using DA Mac 0180.C200.000D";
        }
        enum RF {
          description
            "Reserved Protocol using DA Mac 0180.C200.000F";
        }
      }
    }
  }

  grouping service-instance-rewrite {

    leaf type {
      description "Defines type of rewrite";
      type enumeration {
        enum ingress {
          description
            "Ingress Rewrite";
        }
        enum egress {
          description
            "Egress Rewrite";
        }
      }
    }

    leaf operation {
      description "Defines operation type";
      type enumeration {
        enum pop {
          description
            "Pop the tag";
        }
        enum push {
          description
            "Rewrite Operation of push";
        }
        enum translate {
          description
            "Translate Tag";
        }
      }
    }
  }

  grouping service-instance-bridge-domain {
    leaf value {
      type string;
      description
        "Specifies the BDI interface to use";
    }

    leaf group-number {
      type uint8 {
        range "0 .. 13";
      }
      description
        "Specifies the split-horizon group number";
    }
  }

  grouping statistics-config {
    leaf load-interval {
      type uint32 {
        range "0..600";
      }

      // default "300";

      description
        "Specify interval for load calculation for an
        interface.
        0 disables load calculation, otherwise some
        multiple of 30 between 30 and 600.";
    }
  }

  grouping statistics-state {
    description
      "Damping related operational state";

    //TODO: placeholder for operational state related to statistics
  }

  grouping statistics-top {
    description
      "Top-level grouping for statistics data";

    container statistics {
      description
        "Enclosing container for statistics interface-specific
        data.";

      container config {
          description "Configuration parameters for statistics";

          uses statistics-config;
      }

      container state {

        config false;
        description "State variables for statistics";

        uses statistics-config;
        uses statistics-state;
      }
    }
  }

  grouping rpf-check-top {
    leaf rpf-check {
      type enumeration {
        enum ANY {
          description "Source is reachable via any interface";
        }
        enum RX {
          description "Source is reachable via interface on which
                      packet was received";
        }
      }
    }
  }

  identity RPF_ALLOW_CONFIG_BASE {
    description "Base identity for RPF check config";
  }

  identity RPF_ALLOW_DEFAULT {
    base RPF_ALLOW_CONFIG_BASE;
    description "Base identity for RPF check config";
  }

  identity RPF_ALLOW_SELF_PING {
    base RPF_ALLOW_CONFIG_BASE;
    description "Base identity for RPF check config";
  }

  grouping allow-config-top {
    leaf-list allow-config {
      type identityref {
        base RPF_ALLOW_CONFIG_BASE;
      }
    }
  }

  grouping ipv4-verify {
    container ipv4 {
      uses rpf-check-top;
      uses allow-config-top;
    }

    description "Enables RPF check for ipv4 interface";
  }

  grouping ipv6-verify {
    container ipv6 {
      uses rpf-check-top;
      uses allow-config-top;
    }

    description "Enables RPF check for ipv6 interface";
  }

  grouping verify-unicast-source-reachable-via-top {
    container verify-unicast-source-reachable-via {
      uses ipv4-verify;
      uses ipv6-verify;
    }

    description "Enable per packet validation for unicast,
                reachability check applied to the source
                address";
  }

  // augment statements

  augment "/oc-if:interfaces/oc-if:interface" {
    ext:augment-identifier "if-cisco-stats-aug";
    description "Adds Cisco specific statistics configuration to
                interfaces model";

    uses statistics-top;
  }

  augment "/oc-if:interfaces/oc-if:interface/oc-if:config" {
    ext:augment-identifier "if-cisco-ext-aug";
    description "Adds Cisco specific statistics configuration to
                interfaces model";

    uses cisco-if-extension-config;
  }
  augment "/oc-if:interfaces/oc-if:interface" {
    description "Adds Reverse Path Forwarding (RPF) checking to
                interface model";

    uses verify-unicast-source-reachable-via-top;
  }

  augment "/oc-if:interfaces/oc-if:interface/oc-if:subinterfaces/" +
              "oc-if:subinterface" {
    ext:augment-identifier "if-subif-cisco-stats-aug";
    description "Adds Cisco specific statistics configuration to
                subinterfaces model";

    uses statistics-top;
  }

  augment "/oc-if:interfaces/oc-if:interface/oc-if:subinterfaces/" +
                "oc-if:subinterface/oc-if:config" {
    ext:augment-identifier "if-subif-cisco-ext-aug";
    description "Adds Cisco specific statistics configuration to
               subinterfaces model";

    uses cisco-if-extension-config;
  }

  augment "/oc-if:interfaces/oc-if:interface/oc-if:subinterfaces/" +
              "oc-if:subinterface" {
    ext:augment-identifier "if-subif-cisco-hold-time-aug";
    description "Adds Cisco specific hold-time configuration to
                subinterfaces model";

    uses oc-if:interface-phys-holdtime-top;
  }

  augment "/oc-if:interfaces/oc-if:interface" {
    ext:augment-identifier "if-cisco-service-instance-aug";
    description "Adds Cisco specific service instance
                configuration to interfaces model.";

    uses service-instance-top;
  }

  augment "/oc-if:interfaces/oc-if:interface/oc-eth:ethernet/oc-eth:config" {
    ext:augment-identifier "if-eth-cisco-ext-aug";
    when "oc-if:type = 'ift:ethernetCsmacd'" {
      description "Active when the interface is Ethernet.";
    }

    description "Adds cisco specific lacp rate mode to lacp model.";

    uses cisco-if-eth-extension-config;
  }

  // uniconfig augmentations

  augment "/nt:network-topology/nt:topology/nt:node/ut:configuration/oc-if:interfaces/oc-if:interface" {
    description "Adds Cisco specific statistics configuration to
                    interfaces model";

    uses statistics-top;
  }

  augment "/nt:network-topology/nt:topology/nt:node/ut:configuration/oc-if:interfaces/oc-if:interface/oc-if:config" {
    description "Adds Cisco specific statistics configuration to
                    interfaces model";

    uses cisco-if-extension-config;
  }

  augment "/nt:network-topology/nt:topology/nt:node/ut:configuration/oc-if:interfaces/oc-if:interface" {
    description "Adds Reverse Path Forwarding (RPF) checking to
                interface model";

    uses verify-unicast-source-reachable-via-top;
  }

  augment "/nt:network-topology/nt:topology/nt:node/ut:configuration/oc-if:interfaces/oc-if:interface" +
              "/oc-if:subinterfaces/oc-if:subinterface"{
    description "Adds Cisco specific statistics configuration to
                subinterfaces model";

    uses statistics-top;
  }

  augment "/nt:network-topology/nt:topology/nt:node/ut:configuration/oc-if:interfaces/oc-if:interface" +
              "/oc-if:subinterfaces/oc-if:subinterface/oc-if:config"{
    description "Adds Cisco specific statistics configuration to
                subinterfaces model";

    uses cisco-if-extension-config;
  }
  augment "/nt:network-topology/nt:topology/nt:node/ut:configuration/oc-if:interfaces/oc-if:interface" +
              "/oc-if:subinterfaces/oc-if:subinterface"{
    description "Adds Cisco specific hold-time configuration to
                subinterfaces model";

    uses oc-if:interface-phys-holdtime-top;
  }

  augment "/nt:network-topology/nt:topology/nt:node/ut:configuration/oc-if:interfaces/oc-if:interface" {
    description "Adds Cisco specific service instance
                configuration to interfaces model.";

    uses service-instance-top;
  }

  augment "/nt:network-topology/nt:topology/nt:node/ut:configuration/oc-if:interfaces/oc-if:interface/oc-eth:ethernet/oc-eth:config" {
    when "oc-if:type = 'ift:ethernetCsmacd'" {
      description "Activate when the interface is Ethernet.";
    }

    description "Adds cisco specific lacp rate mode to lacp model.";

    uses cisco-if-eth-extension-config;
  }
}
