module cisco-if-extension {

  yang-version "1";

  // namespace
  namespace "http://frinx.io/yang/interfaces/cisco";

  prefix "cisco-if-ext";

  // import some basic types
  import openconfig-interfaces { prefix oc-if; }
  // uniconfig imports
  import network-topology { prefix nt; revision-date "2013-10-21"; }
  import uniconfig-topology { prefix ut; revision-date "2017-11-21"; }
  import yang-ext { prefix ext; revision-date "2013-07-09"; }

  // meta
  organization "Frinx s.r.o";

  contact
    "support@frinx.io";

  description
    "Set of augments needed to OpenConfig interfaces models,
    containing CISCO specific features.";

  revision "2017-10-24" {
    description
      "Initial release";
    reference "3.1.1";
  }

  // grouping statements

  grouping statistics-config {
    leaf load-interval {
      type uint32 {
        range "0..600";
      }

      default "300";

      description
        "Specify interval for load calculation for an
        interface.
        0 disables load calculation, otherwise some
        multiple of 30 between 30 and 600.";
    }
  }

  grouping statistics-state {
    description
      "Damping related operational state";

    //TODO: placeholder for operational state related to statistics
  }

  grouping statistics-top {
    description
      "Top-level grouping for statistics data";

    container statistics {
      description
        "Enclosing container for statistics interface-specific
        data.";

      container config {
          description "Configuration parameters for statistics";

          uses statistics-config;
      }

      container state {

        config false;
        description "State variables for statistics";

        uses statistics-config;
        uses statistics-state;
      }
    }
  }

  // augment statements

  augment "/oc-if:interfaces/oc-if:interface" {
    ext:augment-identifier "if-cisco-stats-aug";
    description "Adds Cisco specific statistics configuration to
                interfaces model";

    uses statistics-top;
  }

  // uniconfig augmentations

  augment "/nt:network-topology/nt:topology/nt:node/ut:configuration/oc-if:interfaces/oc-if:interface" {
    ext:augment-identifier "uniconfig-node-interfaces-if-cisco-stats-aug";
    description "Adds Cisco specific statistics configuration to
                    interfaces model";

    uses statistics-top;
  }

}
