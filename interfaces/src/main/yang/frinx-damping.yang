module frinx-damping {

  yang-version "1";

  // namespace
  namespace "http://frinx.openconfig.net/yang/damping";

  prefix "damp";

  // import some basic types
  import frinx-openconfig-interfaces { prefix oc-if; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Damping implementation based on OpenConfig interfaces";

  revision "2017-10-24" {
    description
      "Initial release";
    reference "3.1.1";
  }

  // grouping statements

  grouping damping-config {
    leaf enabled {
      type boolean;
      // default "false";
      description
        "Desired state of damping";
    }

    leaf half-life {
      type uint32;
      units "minutes";
      description
        "Decay half life (in minutes).
        Must be less than the max-suppress value.";
    }

    leaf reuse {
      type uint32 {
        range "1..20000";
      }
      description
        "Reuse threshold — Arbitrary value below which
        a suppressed route can be used again.";
    }

    leaf suppress {
      type uint32 {
        range "1..20000";
      }
      description
        "Suppress threshold — Arbitrary value above which
        a route can no longer be used or included in advertisements.
        Must be greater than the reuse threshold.";
    }

    leaf max-suppress {
      type uint32;
      units "minutes";
      description
        "Max suppress time (in minutes)";
    }
  }

  grouping damping-state {
    description
      "Damping related operational state";

    //TODO: placeholder for operational state related to damping
  }

  grouping damping-top {
    description
      "Top-level grouping for damping data";

    container damping {
      description
        "Enclosing container for damping interface-specific
        data.";

      container config {
          description "Configuration parameters for damping";

          uses damping-config;
      }

      container state {

        config false;
        description "State variables for damping";

        uses damping-config;
        uses damping-state;
      }
    }
  }

  // augment statements

  augment "/oc-if:interfaces/oc-if:interface" {
    ext:augment-identifier "if-damp-aug";
    description "Adds additional damping configuration to interfaces model";

    uses damping-top;
  }

  // uniconfig augmentations

  augment "/nt:network-topology/nt:topology/nt:node/ut:configuration/oc-if:interfaces/oc-if:interface" {
    description "Adds additional damping configuration to interfaces model";

    uses damping-top;
  }
}
