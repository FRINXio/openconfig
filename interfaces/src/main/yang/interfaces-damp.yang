module interfaces-damp {

  yang-version "1";

  // namespace
  namespace "http://frinx.io/yang/interfaces/damp";

  prefix "damp";

  // import some basic types
  import openconfig-interfaces { prefix oc-if; }
  import openconfig-if-aggregate { prefix oc-lag; }
  import openconfig-extensions { prefix oc-ext; }

  organization "Frinx s.r.o";

  contact
    "support@frinx.io";

  description
    "Dampening implementation based on Openconfig interfaces";

  revision "2017-10-24" {
    description
      "Initial release";
  }

  grouping damp {
    container damp {
      description
        "Whether this interface's state changes are
        dampened or not";

      leaf enabled {
        type boolean;
        default "false";
        description "Equivalent to dampening command";
      }

      leaf half-life {
        type uint32 {
          range "1..45";
        }
        units "minute";
        description "Decay half life (in minutes)";
      }

      leaf reuse {
        type uint32 {
          range "1..20000";
        }
        description "Reuse threshold";
      }

      leaf suppress {
        type uint32 {
          range "1..20000";
        }
        description "Suppress threshold";
      }

      leaf max-suppress {
        type uint32 {
          range "1..255";
        }
        units "minute";
        description "Max suppress time (in minutes)";
      }
    }
  }

  augment "/oc-if:interfaces/oc-if:interface/oc-if:config/" {
    description
          "Adds configuration items for dampening";

    uses damp;
  }

  augment "/oc-if:interfaces/oc-if:interface/oc-if:state/" {
    description
          "Adds operational items for dampening";

    uses damp;
  }
}
