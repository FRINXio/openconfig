module frinx-cdp {

  yang-version "1";

  // namespace
  namespace "http://frinx.openconfig.net/yang/cdp";

  prefix "cdp";

  import frinx-openconfig-lldp { prefix oc-lldp; }

  // uniconfig imports
  import network-topology { prefix nt; revision-date "2013-10-21"; }
  import frinx-uniconfig-topology { prefix ut; revision-date "2017-11-21"; }

  // meta
  organization "Frinx s.r.o";

  contact
    "support@frinx.io";

  description
    "This module defines configuration and operational state data
    for the CDP protocol. Based on openconfig LLDP";

  revision "2017-10-24" {
    description "Initial revision";
  }

  grouping cdp-top {
    description
      "Top-level grouping for CDP model";

    container cdp {
      description
        "Top-level container for CDP configuration and state data";

      container config {
        description
          "Configuration data ";

        uses oc-lldp:lldp-config;
        uses oc-lldp:lldp-system-info-config;
      }

      container state {

        config false;

        description
          "Operational state data ";

        uses oc-lldp:lldp-config;
        uses oc-lldp:lldp-system-info-config;
        uses oc-lldp:lldp-system-info-state;
        uses oc-lldp:lldp-state;
      }

      uses oc-lldp:lldp-interface-top;
    }
  }

  // data definition statements

  uses cdp-top;

  // uniconfig augmentations

  augment "/nt:network-topology/nt:topology/nt:node/ut:configuration" {
    uses cdp-top;
  }

}
